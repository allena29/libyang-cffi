module minimal-integrationtest {

  namespace "http://mellon-collie.net/yang/minimal-integrationtest";
  prefix "mit";
  import ietf-inet-types { prefix inet; }
  import ietf-yang-metadata { prefix md; }

  description "A yang module to tets the important things of libyang's data nodes";


  md:annotation my-annotation {
    type string;
    description "This is my annotation.";
  }

  md:annotation my-second-annotation {
    type string;
    description "This is my second annotation.";
  }

  container augments {
    container go-in-here {
      presence true;

    }
  }

  container merges {
    presence true;
    leaf a {
      type string;
    }
    leaf b {
      type string;
      must "../a";
    }
  }
  container ip {
    presence true;
    leaf ipv4 {
      type inet:ipv4-prefix;
    }
    list v4 {
      key prefix;
      leaf prefix {
        type inet:ipv4-prefix;
      }
    }
    leaf-list four {
      type inet:ipv4-prefix;
    }
    leaf-list six {
      type inet:ipv6-prefix;
    }
    leaf ipv6 {
      type inet:ipv6-prefix;
    }
    list v6 {
      key prefix;
      leaf prefix {
        type inet:ipv6-prefix;
      }
    }
  }
  container types {
    container when-condition {
      presence true;
      leaf a {
        type string;
        when "../b='a'";
      }
      leaf b {
        type string;
      }
      leaf c {
        type string;
        must "../b='b'";
      }
      leaf-list d {
        type string;
        when "../a='z'";
        must "../b!='a'";
      }
      list e {
        key f;
        leaf g {
          type string;
        }
        leaf f {
          type string;
        }
        when "../a='z'";
        must "../b='brewyork'";

      }
      choice beer {
        case jackhammer {
          leaf bitter {
            type empty;
            must "../b='just-a-couple'";
            when "../c='fancy-something-west-coast'";
          }
        }
        case johnbiscotti {
          leaf pastrystout {
            type empty;
            when "../c='fancy-something-dark'";
            must "../b='have-just-one'";
          }
        }
        when "../c='finished-work'";
      } // end choice
      when "../str1='z'";
      must "../str1!='a'";
      must "../str2!='z'";
    }
    leaf str1 {
      type string;
    }
    leaf str2 {
      type string;
    }
    leaf str3 {
      type string;
    }
    leaf str4 {
      type string;
      default "string4-default";
    }
    leaf enumeratio {
      type enumeration {
        enum A;
        enum Z;
      }
    }
    leaf void {
      type empty;
    }
    leaf bool {
      type boolean;
    }
    leaf dec_64 {
      type decimal64 {
        fraction-digits 3;
      }
    }
    container cont {
      presence false;
    }
    container pcont {
      presence true;
    }
    leaf int_8 {
      type int8;
    }
    leaf int_16 {
      type int16;
    }
    leaf int_32 {
      type int32;
    }
    leaf int_64 {
      type int64;
    }
    leaf u_int_8 {
      type uint8;
    }
    leaf u_int_16 {
      type uint16;
    }
    leaf u_int_32 {
      type uint32;
    }
    leaf u_int_64 {
      type uint64;
    }
    container present {
      presence true;
    }
    list collection {
      key x;
      leaf x {
        type string;
      }
      leaf y {
        type string;
      }
      container z {
        presence true;
        leaf zzz {
          type empty;
        }
      }
      list inner {
        key "a b";
        leaf a {
          type string;
        }
        leaf b {
          type string;
        }
        choice c {
          case d {
            leaf-list e {
              type string;
            }
          }
          case f {
            leaf g {
              type union {
                type enumeration {
                  enum a;
                }
                type boolean;
              }
            }
          }
        }
      }
    }
    leaf-list simplecollection {
      type string;
    }
  }

  list materials {
    key "a b c";
    leaf a {
      type string;
    }
    leaf b {
      type string;
    }
    leaf c {
      type uint32;
    }

    container available {
      presence true;

      leaf factory {
        type string;
        default beer;
      }

      list locations {
        key location;
        leaf location {
          type string;
        }

        list workers  {
          key worker;

          leaf worker {
            type string;
          }

          leaf location {
            type locationtype;
          }

          container personal-info {
            presence true;
            leaf age {
              type uint32;
            }
            leaf salary {
              type enumeration {
                enum underpaid;
                enum overpaid;
              }
            }
          }

          container stats {
            leaf workrate {
              type uint32;
            }
            leaf idle {
              type boolean;
            }
            leaf-list skills {
              type string;
            }

          }
        }

      }
    }
  }

  typedef locationtype {
    type union {
      type enumeration {
        enum uk;
        enum europe;
        enum americas;
      }
      type string;
    }
  }
  list metals {
    key "a b";
    leaf a {
      type string;
    }
    leaf b {
      type string;
    }
    container metal {
      container iron {
        leaf ore {
          default "a";
          type string;
        }
      }
      container nickel {
        leaf coin {
          type string;
          default "b";
        }
      }
      container steel {
        leaf girder {
          type string;
        }
      }
    }
  }
  container nesting {
    container bronze {
      container silver {
        container gold {
          container platinum {
            leaf deep {
              type string;
            }
            leaf deep2 {
               type string;
            }
            leaf deep3 {
              type string;
            }
            leaf deep4 {
              type string;
            }
            leaf deep5 {
              type string;
            }
          }
        }
      }
    }
  }

  container leaf_refs {
    leaf leaf_ref_consumer {
      type leafref {
        path "/mit:leaf_refs/mit:leaf_ref_data/mit:key";
      }
    }

    list leaf_ref_data {
      key "key";

      leaf "key" {
        type string;
      }
    }
  }
}

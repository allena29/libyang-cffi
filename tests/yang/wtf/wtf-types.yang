module wtf-types {
  namespace "urn:yang:wtf:types";
  prefix t;

  typedef str {
    type string;
  }

  typedef host {
    type str;
  }

  typedef unsigned {
    type union {
      type uint16;
      type uint32;
    }
  }

  typedef signed {
    type union {
      type int16;
      type int32;
    }
  }

  typedef number {
    type union {
      type unsigned;
      type signed;
    }
  }

  typedef protocol {
    type enumeration {
      enum http;
      enum https;
      enum ftp;
      enum sftp;
      enum tftp;
    }
  }

  typedef permissions {
    type bits {
      bit read;
      bit write;
      bit execute;
    }
  }

  typedef long-description {
    type verylong-description {
      length "1..127";
      pattern "[A-Za-z].*";
    }
  }

  typedef verylong-description {
    type string {
      length "1..4096";
    }
  }

  typedef custom-protocol {
    type string {
      pattern "user-[A-Z0-9_]" {
        error-message "User defined protocols must start with user- and contain alphanumerics.";
      }
      length "7..15" {
        error-message "Length of field must be 7-15 characters long";
      }
    }
  }
}

module yolo-system {
  namespace "urn:yang:yolo:system";
  prefix sys;

  import omg-extensions { prefix ext; }
  import wtf-types { prefix types; }

  description
    "YOLO.";

  revision 1999-04-01 {
    description
      "Version update.";
    reference "RFC 2549 - IP over Avian Carriers with Quality of Service.";
    ext:human-name "2549";
  }

  revision 1990-04-01 {
    description
      "Initial version.";
    reference "RFC 1149 - A Standard for the Transmission of IP Datagrams on Avian Carriers.";
    ext:human-name "1149";
  }

  feature turbo-boost {
    description
      "Goes faster.";
  }

  grouping tree {
    leaf hostname {
      description
        "The hostname.";
      type types:host;
    }

    leaf deprecated-leaf {
      status deprecated;
      description
        "A deprecated leaf.";
      type string;
    }

    leaf obsolete-leaf {
      status obsolete;
      description
        "An obsolete leaf.";
      type string;
    }

    list url {
      description
        "An URL.";
      key "proto host";
      leaf proto {
        type types:protocol;
      }
      leaf host {
        type string;
      }
      leaf port {
        type uint16;
      }
      leaf path {
        type string;
      }
    }

    leaf-list number {
      description
        "A number.";
      type types:number;
    }

    leaf speed {
      description
        "The speed.";
      if-feature turbo-boost;
      type uint32;
    }
  }

  container conf {
    description
      "Configuration.";
    uses tree;
  }

  container state {
    description
      "State.";
    config false;
    uses tree;
  }

  rpc chmod {
    description
      "Change permissions on path.";
    ext:require-admin;
    input {
      leaf path {
        type string;
      }
      leaf perms {
        type types:permissions;
      }
    }
  }

  rpc format-disk {
    description
      "Format disk.";
    ext:require-admin;
    input {
      leaf disk {
        ext:human-name "Disk";
        type types:str;
      }
    }
    output {
      leaf duration {
        type uint32;
      }
    }
  }

  container user-input {

    leaf field {
      type union {
        type types:protocol;
        type types:custom-protocol;
      }
    }

    leaf short-description {
      type types:long-description {
        length "1..63" {
          error-message "This is a short-description.";
        }
        pattern "Summary: [A-Za-z].*" {
          error-message "Must start with the tag Summary:";
        }
      }
    }

    leaf long-description {
      type types:long-description;
    }

    leaf keywords {
      type string {
        length "1..31";
        pattern "([A-Za-z] ?){1,3}" {
          error-message "3 keywords only";
        }
      }
    }

  }
}
